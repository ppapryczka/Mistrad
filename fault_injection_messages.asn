Fault-Injection-Messages AUTOMATIC TAGS ::= 
BEGIN

  InjectionCollection ::= SEQUENCE {
    injectionActionsNum         Integer(0..4294967295),
    registerInjectionActionsNum Integer(0..4294967295),
    memoryInjectionActionsNum   Integer(0..4294967295)
  }
  
  RegisterInjectionAction ::= SEQUENCE {
    injectionAddress            Integer(0..4294967295),
    registerIndex               Integer(0..15),           -- R0, R1..R12, SP, LR, PC
    valueMask                   Integer(0..4294967295),
    maskOperation               Integer(0..2)             -- SET, XOR, OR
  }

  MemoryInjectionAction ::= SEQUENCE {
    injectionAddress            Integer(0..4294967295),
    memoryAddress               Integer(0..4294967295),
    valueMask                   Integer(0..4294967295),
    maskOperation               Integer(0..2)             -- SET, XOR, OR
  }

END
